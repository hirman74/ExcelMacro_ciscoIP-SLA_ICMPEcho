RFC-1212 DEFINITIONS ::= BEGIN

	IMPORTS
				 ObjectName
					 FROM RFC1155-SMI
				 DisplayString
					 FROM RFC1158-MIB;

			 OBJECT-TYPE MACRO ::=
			 BEGIN
				 TYPE NOTATION ::=
											 -- must conform to
											 -- RFC1155 's ObjectSyntax
								   "SYNTAX" type(ObjectSyntax)
								   "ACCESS" Access
								   "STATUS" Status
								   DescrPart
								   ReferPart
								   IndexPart
								   DefValPart
				 VALUE NOTATION ::= value (VALUE ObjectName)

				 Access ::= "read-only"
								 | "read-write"
								 | "write-only"
								 | "not-accessible"
				 Status ::= "mandatory"
								 | "optional"
								 | "oobsolete"
								 | "deprecated"

				 DescrPart ::=
							"DESCRIPTION" value (description DisplayString)
								 | empty

				 ReferPart ::=
							"REFERENCE" value (reference DisplayString)
								 | empty

				 IndexPart ::=
							"INDEX" "{" IndexTypes "}"

								 | empty
				 IndexTypes ::=
							IndexType | IndexTypes "," IndexType

				 IndexType ::=
									 -- if indexobject, use the SYNTAX
									 -- value of the correspondent
									 -- OBJECT-TYPE invocation
							value (indexobject ObjectName)
									 -- otherwise use named SMI type
									 -- must conform to IndexSyntax below
								 | type (indextype)

				 DefValPart ::=
							"DEFVAL" "{" value (defvalue ObjectSyntax) "}"
								 | empty

			 END

			 IndexSyntax ::=
				 CHOICE {
					 number
						 INTEGER (0..MAX),
					 string
						 OCTET STRING,
					 object
						 OBJECT IDENTIFIER,
					 address
						 NetworkAddress,
					 ipAddress
						 IpAddress
				 }


				  -- names of objects in the MIB

	--               ObjectName ::=
	--                   OBJECT IDENTIFIER


				  -- syntax of objects in the MIB

				  ObjectSyntax ::=
					  CHOICE {
						  simple
							  SimpleSyntax,

				  -- note that simple SEQUENCEs are not directly
				  -- mentioned here to keep things simple (i.e.,
				  -- prevent mis-use).  However, application-wide
				  -- types which are IMPLICITly encoded simple
				  -- SEQUENCEs may appear in the following CHOICE

						  application-wide
							  ApplicationSyntax
					  }

					 SimpleSyntax ::=
						 CHOICE {
							 number
								 INTEGER,

							 string
								 OCTET STRING,

							 object
								 OBJECT IDENTIFIER,

							 empty
								 NULL
						 }

					 ApplicationSyntax ::=
						 CHOICE {
							 address
								 NetworkAddress,

							 counter
								 Counter,

							 gauge
								 Gauge,

							 ticks
								 TimeTicks,

							 arbitrary
								 Opaque


					 -- other application-wide types, as they are
					 -- defined, will be added here
						 }


					 -- application-wide types

					 NetworkAddress ::=
						 CHOICE {
							 internet
								 IpAddress
						 }

					 IpAddress ::=
						 [APPLICATION 0]          -- in network-byte order
							 IMPLICIT OCTET STRING (SIZE (4))

					 Counter ::=
						 [APPLICATION 1]
							 IMPLICIT INTEGER (0..4294967295)

					 Gauge ::=
						 [APPLICATION 2]
							 IMPLICIT INTEGER (0..4294967295)

					 TimeTicks ::=
						 [APPLICATION 3]
							 IMPLICIT INTEGER (0..4294967295)

					 Opaque ::=
						 [APPLICATION 4]          -- arbitrary ASN.1 value,
							 IMPLICIT OCTET STRING   --   "double-wrapped"

					 END
